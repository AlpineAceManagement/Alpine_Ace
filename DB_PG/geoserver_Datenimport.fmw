FME workspace geoserver_Datenimport.fmw

Parameters:
- SourceDataset_OGCGEOPACKAGE = $(FME_MF_DIR)gpkg_Daten\Pisten_OSM.gpkg   # GeoPackage File
- SourceDataset_OGCGEOPACKAGE_5 = $(FME_MF_DIR)gpkg_Daten\Anlagen.gpkg   # GeoPackage File
- SourceDataset_OGCGEOPACKAGE_7 = $(FME_MF_DIR)gpkg_Daten\Pisten_OSM.gpkg   # GeoPackage File
- DestDataset_POSTGIS_13 = geoserver   # Connection
- DestDataset_POSTGIS_21 = geoserver   # Connection
- DestDataset_POSTGIS_17 = geoserver   # Connection
- DestDataset_POSTGIS_19 = geoserver   # Connection
- DestDataset_POSTGIS_23 = geoserver   # Connection
- DestDataset_POSTGIS_15 = geoserver   # Connection
- SourceDataset_CSV2 = $(FME_MF_DIR)CSV_Daten\Restaurants_Arosa_Lenzerheide.csv   # Source CSV (Comma Separated Value) File(s)
- DestDataset_POSTGIS_16 = geoserver   # Connection
- SourceDataset_CSV2_9 = $(FME_MF_DIR)CSV_Daten\Parkplatz.csv   # Source CSV (Comma Separated Value) File(s)
- DestDataset_POSTGIS_14 = geoserver   # Connection
- SourceDataset_CSV2_7 = $(FME_MF_DIR)CSV_Daten\OeV.csv   # Source CSV (Comma Separated Value) File(s)
- DestDataset_POSTGIS_18 = geoserver   # Connection
- SourceDataset_CSV2_6 = $(FME_MF_DIR)CSV_Daten\meteo_stationen.csv   # Source CSV (Comma Separated Value) File(s)
- DestDataset_POSTGIS_20 = geoserver   # Connection
- SourceDataset_TEXTLINE = $(FME_MF_DIR)geoserver_DB_erstellen.txt   # Source Text File(s)
- DestDataset_POSTGIS = geoserver   # Connection
- min_hoehenunterschied_Pisten = 15   # Minimaler Höhenunterschied für Analgen Orientierung Einweg
- min_hoehenunterschied_Anlagen = 5   # Right Value
- SourceDataset_ESRIASCIIGRID = $(FME_MF_DIR)ASCII_Hoehenmodell\dhm25_grid_raster.asc   # Source Esri ASCII Grid File(s)

Readers:
- TEXTLINE_1: TEXTLINE from $(SourceDataset_TEXTLINE)
- OGCGEOPACKAGE_1: OGCGEOPACKAGE from $(SourceDataset_OGCGEOPACKAGE) in EPSG:2056
- OGCGEOPACKAGE_2: OGCGEOPACKAGE from $(SourceDataset_OGCGEOPACKAGE_5) in EPSG:2056
- OGCGEOPACKAGE_3: OGCGEOPACKAGE from $(SourceDataset_OGCGEOPACKAGE_7)
- ESRIASCIIGRID_1: ESRIASCIIGRID from $(SourceDataset_ESRIASCIIGRID) in EPSG:21781
- CSV2_1: CSV2 from $(SourceDataset_CSV2) in EPSG:4326
- CSV2_2: CSV2 from $(SourceDataset_CSV2_9) in EPSG:2056
- CSV2_3: CSV2 from $(SourceDataset_CSV2_7) in EPSG:2056
- CSV2_4: CSV2 from $(SourceDataset_CSV2_6)

Writers:
- POSTGIS_3: POSTGIS to $(DestDataset_POSTGIS_13) in EPSG:2056
- POSTGIS_1: POSTGIS to $(DestDataset_POSTGIS)
- POSTGIS_4: POSTGIS to $(DestDataset_POSTGIS_21) in EPSG:2056
- POSTGIS_2: POSTGIS to $(DestDataset_POSTGIS_17) in EPSG:2056
- POSTGIS_7: POSTGIS to $(DestDataset_POSTGIS_23) in EPSG:2056
- POSTGIS_5: POSTGIS to $(DestDataset_POSTGIS_15) in EPSG:2056
- POSTGIS_6: POSTGIS to $(DestDataset_POSTGIS_19) in EPSG:2056
- POSTGIS_9: POSTGIS to $(DestDataset_POSTGIS_16) in EPSG:2056
- POSTGIS_8: POSTGIS to $(DestDataset_POSTGIS_14) in EPSG:2056
- POSTGIS_10: POSTGIS to $(DestDataset_POSTGIS_18) in EPSG:2056
- POSTGIS_11: POSTGIS to $(DestDataset_POSTGIS_20) in EPSG:2056

Note: Reihenfolge Ablauf Import Export / 1. DB erstellen mittels Master DB File / 2. Import Daten in Workbench / 3: Export Skigebiet in DB als erstes, da praktisch alle Daten mit dem Skigebiet verknüpft sind / 4. Export Pisten /Anlagen, danch die Start/Endpunkte, da diese mit den Pisten/Anlagen verknüpft sind / 5. Export der Restaurants, Parkplätze, ÖV-Haltestelle und Meteo-Stationen
Note: OSM: Linien
planet_pistesosm__lines (reader OGCGEOPACKAGE_1)
    attributes: osm_id text, name text, highway text, waterway text, aerialway text, barrier text, man_made text, railway text, z_order mediumint, other_tags text, UUID text(38), DATUM_AEND date, DATUM_ERST date, ERSTELL_J int, ERSTELL_M text(20), REVISION_J int, REVISION_M text(20), GRUND_AEND text(20), HERKUNFT text(20), HERKUNFT_J int, HERKUNFT_M text(20), OBJEKTART text(20), REVISION_Q text(100), ICC text(20), SEE_FLAECH double, NAME_2 text(254), EINWOHNERZ int, LANDESFLAE double, LAND_TEIL text(20), fid int,PrimaryKey
    -> Tester
Note: herausfiltern aller Pisten
Note: Regeoserver Database Connection / Unter Tools -> FME Options -> Database Connections / Verbindung Geoserver anpassen auf Einstellungen Server: / Host: / Port: / Databasename: / Username: / Password:
Tester
    BOOL_OP = OR
    TEST_CLAUSE = CASE_INSENSITIVE_TEST @Value(other_tags) CONTAINS piste:difficulty
    TEST_MODE = CASE_INSENSITIVE_TEST
    PASSED -> StringSearcher
Note: counter id / Global Domain: counter / Pisten und Anlagen haben gemeinsam einzigarte id's. Dies ermöglicht das debugen, wäre aber nicht nötig.
Junction
    -> StringSearcher_4
Note: Multiline-Pisten in Linien umwandeln
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Counter
Note: piste_id erstellen
Counter
    CNT_ATTR = piste_id
    DOMAIN = counter
    SCOPE = Global
    START = 1
    -> AttributeRenamer_3
Note: name in p_name umbennen
AttributeRenamer_3
    ATTR_TABLE = RENAME_SET_DEFAULT name > p_name
    MISSING_INPUT_ATTRS = REMOVE
    -> AttributeRemover
Note: nicht notwendige OSM Attribute löschen
AttributeRemover
    REMOVE_ATTRS = _first_match,_substring,aerialway,barrier,DATUM_AEND,DATUM_ERST,EINWOHNERZ,ERSTELL_J,ERSTELL_M,GRUND_AEND,HERKUNFT,HERKUNFT_J,HERKUNFT_M,highway,ICC,LAND_TEIL,LANDESFLAE,man_made,NAME_2,OBJEKTART,osm_id,other_tags,railway,REVISION_J,REVISION_M,REVISION_Q,SEE_FLAECH,UUID,waterway,z_order,fid
    -> CoordinateSystemSetter_2
Note: EPSG:2056 setzten
CoordinateSystemSetter_2
    COORDSYS = EPSG:2056
    -> Höhe_Start_und_Endpunkt_herausfinder_Pisten [Linen_EPSG:2056]
Note: TLM3D oev uebrige bahn
tlm_oev_uebrige_bahn (reader OGCGEOPACKAGE_2)
    attributes: id int, uuid text(38), datum_aenderung date, datum_erstellung date, erstellung_jahr mediumint, erstellung_monat mediumint, grund_aenderung text(50), herkunft text(50), herkunft_jahr mediumint, herkunft_monat mediumint, objektart text(50), revision_jahr mediumint, revision_monat mediumint, revision_qualitaet text(50), tlm_oev_name_uuid text(38), name text(254), ausser_betrieb text(10), stufe text(5), betriebsbahn text(10), eroeffnungsdatum date, fid int,PrimaryKey
    -> Counter_2
Note: anlage_id erstellen
Counter_2
    CNT_ATTR = anlage_id
    DOMAIN = counter
    SCOPE = Global
    START = 1
    -> AttributeRenamer_7
Note: name in a_name umbennen
AttributeRenamer_7
    ATTR_TABLE = RENAME_SET_DEFAULT name > a_name
    MISSING_INPUT_ATTRS = REMOVE
    -> CoordinateSystemSetter_3
Note: EPSG:2056 setzten
CoordinateSystemSetter_3
    COORDSYS = EPSG:2056
    -> Höhe_Start_und_Endpunkt_herausfinder_2 [Linen_EPSG:2056]
Note: ESRI ASCII GRID : dhm25_grid_raster.asc / Koordinatensystem EPSG:21781 / (Geländemodell der Schweiz)
ESRIASCIIGRID (reader ESRIASCIIGRID_1)
    -> Höhe_Start_und_Endpunkt_herausfinder_Pisten [Höhenmodell_EPSG:21781]
    -> Höhe_Start_und_Endpunkt_herausfinder_2 [Höhenmodell_EPSG:21781]
Höhe_Start_und_Endpunkt_herausfinder_Pisten
    PISTE_ID = @Value(piste_id)
    Linien_mit_Start_Endpunkten_koord_EPSG:2056 -> SpatialRelator [Requestor]
Höhe_Start_und_Endpunkt_herausfinder_2
    PISTE_ID = @Value(anlage_id)
    Linien_mit_Start_Endpunkten_koord_EPSG:2056 -> SpatialRelator_2 [Requestor]
Note: OSM: Polygone
planet_pistesosm__multipolygons (reader OGCGEOPACKAGE_3)
    attributes: osm_id text, osm_way_id text, name text, type text, aeroway text, amenity text, admin_level text, barrier text, boundary text, building text, craft text, geological text, historic text, land_area text, landuse text, leisure text, man_made text, military text, natural text, office text, place text, shop text, sport text, tourism text, other_tags text, UUID text(38), DATUM_AEND date, DATUM_ERST date, ERSTELL_J int, ERSTELL_M text(20),
      REVISION_J int, REVISION_M text(20), GRUND_AEND text(20), HERKUNFT text(20), HERKUNFT_J int, HERKUNFT_M text(20), OBJEKTART text(20), REVISION_Q text(100), ICC text(20), SEE_FLAECH double, NAME_2 text(254), EINWOHNERZ int, LANDESFLAE double, LAND_TEIL text(20), fid int,PrimaryKey
    -> CoordinateSystemSetter
Note: EPSG:2056 setzten
CoordinateSystemSetter
    COORDSYS = EPSG:2056
    -> Tester_6
Note: Nur Flächen, die keine Pisten sind
Tester_6
    BOOL_OP = AND
    TEST_CLAUSE:
      TEST landuse NOT_ATTRIBUTE_VALUE_NULL ""
      TEST @Value(landuse) NOT_= piste
    TEST_MODE = TEST
    PASSED -> AttributeRemover_5
Note: nicht notwendige OSM Attribute löschen
AttributeRemover_5
    REMOVE_ATTRS = admin_level,aeroway,amenity,barrier,boundary,building,craft,DATUM_AEND,DATUM_ERST,EINWOHNERZ,ERSTELL_J,ERSTELL_M,fid,geological,GRUND_AEND,HERKUNFT,HERKUNFT_J,HERKUNFT_M,historic,ICC,land_area,LAND_TEIL,LANDESFLAE,landuse,leisure,man_made,military,NAME_2,natural,OBJEKTART,office,osm_id,osm_way_id,other_tags,place,REVISION_J,REVISION_M,REVISION_Q,SEE_FLAECH,shop,sport,tourism,type,UUID
    -> AttributeRenamer_6
Note: name umbennen in skigebiet_name für DB
AttributeRenamer_6
    ATTR_TABLE = RENAME_SET_DEFAULT name > skigebiet_name
    MISSING_INPUT_ATTRS = REMOVE
    -> Tester_4
Note: aussortieren der Skigebiete ohne Namen
Tester_4
    BOOL_OP = OR
    TEST_CLAUSE = TEST skigebiet_name NOT_ATTRIBUTE_VALUE_NULL ""
    TEST_MODE = TEST
    PASSED -> Counter_3
Note: skigebiet_id erstellen
Counter_3
    CNT_ATTR = skigebiet_id
    DOMAIN = counter
    SCOPE = Global
    START = 1
    -> Junction_13
    -> skigebiet (writer POSTGIS_3)
    -> Junction_15
    -> Junction_11
Note: führt zu Anlagen
Junction_13
    -> Junction_14
Note: SpatialRelator_3 : Supplier
Junction_11
    -> Junction_12
Note: Skigebiete
Junction_12
    -> NeighborFinder_3 [CANDIDATE]
    -> NeighborFinder_2 [CANDIDATE]
    -> NeighborFinder [CANDIDATE]
    -> NeighborFinder_4 [CANDIDATE]
Note: führt zu Pisten
Junction_15
    -> Junction_16
Note: CSV: Meteostationen
CSV (reader CSV2_4)
    attributes: Code varchar(4), Label varchar(24), Longitude x_coordinate, Latitude y_coordinate
    -> VertexCreator_14
Note: Punkte erstellen aus Attribtuen Lägnen/Breitengrad
VertexCreator_14
    MEASURE_TYPE = Continuous
    MODE_NAME = Replace with Point
    XVAL = @Value(Longitude)
    YVAL = @Value(Latitude)
    -> CoordinateSystemSetter_7
Note: EPSG:4326 setzten
CoordinateSystemSetter_7
    COORDSYS = EPSG:4326
    -> Reprojector_4
Note: in EPSG:2056 umprojizieren
Reprojector_4
    DEST = EPSG:2056
    INTERPOLATION_TYPE_NAME = Nearest Neighbor
    RASTER_CELL_SIZE = Preserve Cells
    RASTER_TOLERANCE = 0.0
    SOURCE = EPSG:4326
    REPROJECTED -> NeighborFinder [BASE]
Note: skigebiet_id wird für den Datenbank import benötig um Elemente am Skigebiet zu verknüpfen
Note: Attribute für Datenbank import umbennen
AttributeManager_6
    ATTR_TABLE:
      RENAME_SET_VALUE Code > station_id (varchar(4))
      RENAME_SET_VALUE Label > s_name (varchar(24))
    -> station (writer POSTGIS_11)
Note: CSV: Restuarant
CSV (reader CSV2_1)
    attributes: restaurant_id uint32, r_name varchar(40), r_geometry varchar(37), r_oeffnungszeiten varchar(11), r_telefon varchar(17), r_email varchar(45), r_webseite varchar(78), r_dateipfad_bildname varchar(82)
    -> CSV_WGS_to_LV95_Restaurant [CSV_WGS84]
CSV_WGS_to_LV95_Restaurant
    DELIMITER = ,
    R_GEOMETRY = @Value(r_geometry)
    LV95 -> NeighborFinder_4 [BASE]
Note: CSV: Parkpaltz
CSV (reader CSV2_2)
    attributes: parkplatz_id uint32, pp_name varchar(23), pp_geometrie varchar(37)
    -> CSV_WGS_to_LV95_Parkplatz [CSV_WGS84]
CSV_WGS_to_LV95_Parkplatz
    DELIMITER = ,
    R_GEOMETRY = @Value(pp_geometrie)
    LV95 -> NeighborFinder_3 [BASE]
Note: CSV: ÖV Haltestelle
CSV (reader CSV2_3)
    attributes: oev_id uint32, o_name varchar(26), o_geometrie varchar(37)
    -> CSV_WGS_to_LV95_OV [CSV_WGS84]
CSV_WGS_to_LV95_OV
    DELIMITER = ,
    R_GEOMETRY = @Value(o_geometrie)
    LV95 -> NeighborFinder_2 [BASE]

Bookmark: Datenbank erstellen mit Maser DB File
text_line (reader TEXTLINE_1)
    attributes: text_line_data buffer
    -> SQLExecutor [INITIATOR]
SQLExecutor
    COMBINE_ATTRS = Result Attributes Only
    COMBINE_GEOM = Initiator Geometry Only
    DATASET = geoserver
    FORMAT = POSTGIS
    OUTPUT_FEATURES_DISPLAY = Schema and Data Features
    POSTGIS_CREATE_FEATURE_TABLES_FROM_DATA = Yes
    POSTGIS_DISABLE_COLLECTION_SPLITTING = yes
    POSTGIS_NAMED_CONNECTION = geoserver
    POSTGIS_QUERY_FEATURE_TYPES_FOR_MERGE_FILTERS = Yes
    POSTGIS_READ_TIME_WITH_TIMEZONE = Yes
    POSTGIS_SCHEMAS_FOR_TABLE_LISTING = public
    POSTGIS_USE_TRUE_POSTGIS_TYPES = yes
    SQL_STATEMENT = @Value(text_line_data)

Bookmark: Blaue Pisten
StringSearcher
    CASE = no
    MATCHED_RESULT_ATTR = _first_match
    REGEXP = "piste:difficulty"=>"easy"
    STRING_TO_SEARCH = @Value(other_tags)
    MATCHED -> AttributeCreator
    NOT_MATCHED -> StringSearcher_2
AttributeCreator
    ATTR_TABLE = SET_TO p_farbe = Blau
    -> Junction

Bookmark: Rote Pisten
StringSearcher_2
    CASE = no
    MATCHED_RESULT_ATTR = _first_match
    REGEXP = "piste:difficulty"=>"intermediate"
    STRING_TO_SEARCH = @Value(other_tags)
    MATCHED -> AttributeCreator_2
    NOT_MATCHED -> StringSearcher_3
AttributeCreator_2
    ATTR_TABLE = SET_TO p_farbe = Rot
    -> Junction

Bookmark: Schwarze Pisten
StringSearcher_3
    CASE = no
    MATCHED_RESULT_ATTR = _first_match
    REGEXP = "piste:difficulty"=>"advanced"
    STRING_TO_SEARCH = @Value(other_tags)
    MATCHED -> AttributeCreator_3
AttributeCreator_3
    ATTR_TABLE = SET_TO p_farbe = Schwarz
    -> Junction

Bookmark: Pisten nur mit Nummern
StringSearcher_4
    CASE = yes
    MATCHED_RESULT_ATTR = _first_match
    REGEXP = "ref"=>"([0-9]+)"
    STRING_TO_SEARCH = @Value(other_tags)
    MATCHED -> SubstringExtractor
    NOT_MATCHED -> Junction_6
SubstringExtractor
    END = -2
    RESULT_ATTR = _substring
    SRC_STRING = @Value(_first_match)
    START = 8
    -> AttributeCreator_4
AttributeCreator_4
    ATTR_TABLE = SET_TO p_nummer = @Value(_substring)
    -> Junction_6

Bookmark: Pisten mit Nummern und Buchstaben
Junction_6
    -> StringSearcher_5
StringSearcher_5
    CASE = yes
    MATCHED_RESULT_ATTR = _first_match
    REGEXP = "ref"=>"([0-9]+)[a-z]"
    STRING_TO_SEARCH = @Value(other_tags)
    MATCHED -> SubstringExtractor_2
    NOT_MATCHED -> Junction_7
SubstringExtractor_2
    END = -2
    RESULT_ATTR = _substring
    SRC_STRING = @Value(_first_match)
    START = 8
    -> AttributeCreator_5
AttributeCreator_5
    ATTR_TABLE = SET_TO p_nummer = @Value(_substring)
    -> Junction_7
Junction_7
    -> StringSearcher_6

Bookmark: Pisten mit Nummer in Namen
StringSearcher_6
    CASE = no
    MATCHED_RESULT_ATTR = _first_match
    REGEXP = \d+
    STRING_TO_SEARCH = @Value(name)
    MATCHED -> AttributeManager_3
    NOT_MATCHED -> Deaggregator_2
AttributeManager_3
    ATTR_TABLE:
      SET_TO p_nummer (buffer) = @Value(_first_match)
      REMOVE _first_match (buffer)
    -> Deaggregator_2

Bookmark: Analge innerhalb von Skigebiet mit Namen
Note: Skigebiete
Junction_14
    -> SpatialRelator_2 [Supplier]
SpatialRelator_2
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = WITHIN CONTAINS EQUALS INTERSECTS TOUCHES
    SUCCESS_ATTR = _related_suppliers
    -> Tester_7
Note: Nur Anlagen innerhalb des Skigebietes (für Datenbank notwendig)
Tester_7
    BOOL_OP = OR
    TEST_CLAUSE = TEST @Value(_related_suppliers) != 0
    TEST_MODE = TEST
    PASSED -> ExpressionEvaluator
    PASSED -> VertexCreator_8
    PASSED -> VertexCreator_7

Bookmark: Pisten Start/Endpunkte in DB speichern
Note: Endpunkt erstellen
VertexCreator_8
    MEASURE_TYPE = Continuous
    MODE_NAME = Replace with Point
    XVAL = @Value(_start_x)
    YVAL = @Value(_start_y)
    -> anlagen_startpunkt (writer POSTGIS_5)
Note: Startpunkt estellen
VertexCreator_7
    MEASURE_TYPE = Continuous
    MODE_NAME = Replace with Point
    XVAL = @Value(_end_x)
    YVAL = @Value(_end_y)
    -> anlagen_endpunkt (writer POSTGIS_6)

Bookmark: Writer Post-GIS Datenbank Geoserver
anlagen_startpunkt (writer POSTGIS_5)
    attributes: anlage_id int4
anlagen_endpunkt (writer POSTGIS_6)
    attributes: anlage_id int4
anlagen (writer POSTGIS_7)
    attributes: anlage_id serial,PrimaryKey, a_name varchar(50), a_hoehe float8, a_status bool, skigebiet_id int4
skigebiet (writer POSTGIS_3)
    attributes: skigebiet_id serial,PrimaryKey, sg_name varchar(50)
pisten_endpunkt (writer POSTGIS_2)
    attributes: piste_id int4
pisten_startpunkt (writer POSTGIS_4)
    attributes: piste_id int4
pisten (writer POSTGIS_1)
    attributes: piste_id int4,PrimaryKey, p_name varchar(50), p_nummer varchar(5), p_farbe text, p_status bool, p_einweg bool, skigebiet_id int4
station (writer POSTGIS_11)
    attributes: station_id varchar(4),PrimaryKey, s_name text, skigebiet_id int4
restaurant (writer POSTGIS_9)
    attributes: restaurant_id serial,PrimaryKey, r_name varchar(50), r_oeffnungszeiten text, r_telefon char(15), r_email varchar(50), r_webseite text, r_dateipfad_bildname text, skigebiet_id int4
parkplatz (writer POSTGIS_8)
    attributes: parkplatz_id int4,PrimaryKey, pp_name text, skigebiet_id int4
oev (writer POSTGIS_10)
    attributes: oev_id int4,PrimaryKey, o_name text, skigebiet_id int4

Bookmark: Orientierung Piste minimaler Höhenunterscheid festlegen
Note: Höhenunterschied zwischen Startpunkt und Endpunkt berechnen
ExpressionEvaluator
    ACTION = Create New Attribute
    EXPRESSION = @Value(_end_z)-@Value(_start_z)
    VAL_ATTR = a_hoehe
    -> Tester_9
Note: Minimaler Höhenunterschied für Analgen Einweg festellegen
Tester_9
    BOOL_OP = OR
    TEST_CLAUSE = TEST @Value(a_hoehe) > $(min_hoehenunterschied_Anlagen)
    TEST_MODE = TEST
    PASSED -> AttributeManager_9
    FAILED -> AttributeManager_10
Note: a_einweg auf true legen, da Höhenunterschied genug gross
AttributeManager_9
    ATTR_TABLE = SET_TO a_einweg (buffer) = true
    -> anlagen (writer POSTGIS_7)
Note: p_einweg auf false legen, da Höhenunterschied zu klein
AttributeManager_10
    ATTR_TABLE:
      SET_TO a_einweg (buffer) = false
      SET_TO
    -> anlagen (writer POSTGIS_7)

Bookmark: Pisten innerhalb von Skigebiet mit Namen, allle andern Pisten werden nicht weiter benutzt
Note: Skigebiete
Junction_16
    -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = WITHIN CONTAINS EQUALS INTERSECTS TOUCHES
    SUCCESS_ATTR = _related_suppliers
    -> Tester_5
Note: Pisten bei dem Start/Endpunkt keine Höhe haben (Wert=-9999) werden aussortiert
Tester_5
    BOOL_OP = OR
    TEST_CLAUSE:
      TEST @Value(_end_z) != -9999
      TEST @Value(_start_z) != -9999
    TEST_MODE = TEST
    PASSED -> Tester_12
Note: Nur Pisten innerhalb des Skigebietes (für Datenbank notwendig)
Tester_12
    BOOL_OP = OR
    TEST_CLAUSE = TEST @Value(_related_suppliers) != 0
    TEST_MODE = TEST
    PASSED -> Junction_10
Junction_10
    -> VertexCreator_5
    -> VertexCreator_6
    -> ExpressionEvaluator_2

Bookmark: Pisten Start/Endpunkte in DB speichern
Note: Endpunkt erstellen
VertexCreator_5
    MEASURE_TYPE = Continuous
    MODE_NAME = Replace with Point
    XVAL = @Value(_end_x)
    YVAL = @Value(_end_y)
    -> pisten_endpunkt (writer POSTGIS_2)
Note: Startpunkt estellen
VertexCreator_6
    MEASURE_TYPE = Continuous
    MODE_NAME = Replace with Point
    XVAL = @Value(_start_x)
    YVAL = @Value(_start_y)
    -> pisten_startpunkt (writer POSTGIS_4)

Bookmark: Orientierung Piste minimaler Höhenunterscheid festlegen
Note: Höhenunterschied zwischen Startpunkt und Endpunkt berechnen
ExpressionEvaluator_2
    ACTION = Create New Attribute
    EXPRESSION = @Value(_start_z)-@Value(_end_z)
    VAL_ATTR = _h_diff
    -> Tester_8
Note: Minimaler Höhenunterschied für Pisten Einweg festellegen
Tester_8
    BOOL_OP = OR
    TEST_CLAUSE = TEST @Value(_h_diff) > $(min_hoehenunterschied_Pisten)
    TEST_MODE = TEST
    PASSED -> AttributeManager_7
    FAILED -> AttributeManager_8
Note: p_einweg auf true legen, da Höhenunterschied genug gross
AttributeManager_7
    ATTR_TABLE:
      SET_TO p_einweg (buffer) = true
      SET_TO
    -> pisten (writer POSTGIS_1)
Note: p_einweg auf false legen, da Höhenunterschied zu klein
AttributeManager_8
    ATTR_TABLE:
      SET_TO p_einweg (buffer) = false
      SET_TO
    -> pisten (writer POSTGIS_1)

Bookmark: Nächstes Skigebiet finden
NeighborFinder
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Areas
    MATCHED -> AttributeManager_6
NeighborFinder_4
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Areas
    MATCHED -> restaurant (writer POSTGIS_9)
NeighborFinder_3
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Areas
    MATCHED -> parkplatz (writer POSTGIS_8)
NeighborFinder_2
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Areas
    MATCHED -> oev (writer POSTGIS_10)

FME custom transformer Höhe_Start_und_Endpunkt_herausfinder

Parameters:
- PISTE_ID = @Value(piste_id)   # Piste Id

Linen_EPSG:2056 (input)
    -> CoordinateExtractor_3
    -> CoordinateExtractor_4
    -> Junction_2
Note: führt weiter nach vorne, wenn Original Geometreien gebraucht werden
Junction_2
    -> Junction_3
Note: Original Linien
Junction_3
    -> Junction
Note: Vekordaten umwandeln in EPSG:21781, da dass Raster in LV03 Koordianten ist. Die Geometrien werden später nicht mehr verwendet, da diese mit den Original Linen verknüpft werden. Deshalb müssen die Daten nicht mehr zurück in LV95 Geometiren umgewnadelt werden
Höhenmodell_EPSG:21781 (input)
    -> PointOnRasterValueExtractor [RASTER]
    -> PointOnRasterValueExtractor_2 [RASTER]
Note: Über Höhe herausfinden welcher Punkt der Start ist und das Ende
Tester_2
    BOOL_OP = OR
    TEST_CLAUSE = TEST @Value(_z_-1) > @Value(_z_1)
    TEST_MODE = TEST
    PASSED -> AttributeManager
    FAILED -> AttributeManager_2
Linien_mit_Start_Endpunkten_koord_EPSG:2056 (output)

Bookmark: Bisheriger Endpunkt bestimmen
CoordinateExtractor_3
    IND = -1
    MODE = Specify Coordinate
    X_ATTR = _x_-1
    Y_ATTR = _y_-1
    -> VertexCreator_3
VertexCreator_3
    MEASURE_TYPE = Continuous
    MODE_NAME = Replace with Point
    XVAL = @Value(_x_-1)
    YVAL = @Value(_y_-1)
    -> Reprojector

Bookmark: Vekordaten umwandeln in LV03
Reprojector
    DEST = EPSG:21781
    INTERPOLATION_TYPE_NAME = Nearest Neighbor
    RASTER_CELL_SIZE = Preserve Cells
    RASTER_TOLERANCE = 0.0
    SOURCE = EPSG:2056
    REPROJECTED -> PointOnRasterValueExtractor [POINT]
Reprojector_2
    DEST = EPSG:21781
    INTERPOLATION_TYPE_NAME = Nearest Neighbor
    RASTER_CELL_SIZE = Preserve Cells
    RASTER_TOLERANCE = 0.0
    SOURCE = EPSG:2056
    REPROJECTED -> PointOnRasterValueExtractor_2 [POINT]

Bookmark: Bisheriger Startpunkt bestimmen
CoordinateExtractor_4
    IND = 0
    MODE = Specify Coordinate
    X_ATTR = _x_0
    Y_ATTR = _y_0
    -> VertexCreator_4
VertexCreator_4
    MEASURE_TYPE = Continuous
    MODE_NAME = Replace with Point
    XVAL = @Value(_x_0)
    YVAL = @Value(_y_0)
    -> Reprojector_2

Bookmark: Korrekte Koordiante zuweisen, Linie richtig Orientieren
Junction
    -> FeatureJoiner_2 [LEFT]
    -> FeatureJoiner_5 [LEFT]
Note: Start/Endpunkt Koordinaten umbennen
AttributeManager
    ATTR_TABLE:
      RENAME_SET_VALUE _z_-1 > _start_z (real64)
      RENAME_SET_VALUE _x_-1 > _start_x (real64)
      RENAME_SET_VALUE _y_-1 > _start_y (real64)
      REMOVE palette{}.value (real64)
      RENAME_SET_VALUE _z_1 > _end_z (real64)
      RENAME_SET_VALUE _x_0 > _end_x (real64)
      RENAME_SET_VALUE _y_0 > _end_y (real64)
    -> FeatureJoiner_2 [RIGHT]
Note: Startpunkt/Endpunkt Information mit Linie Joinen
FeatureJoiner_2
    ATTR_CONFLICT_RES = Prefer Left
    GEOMETRY_HANDLING = Prefer Left
    JOIN_KEYS = piste_id piste_id AUTO
    JOIN_MODE = Inner
    JOINED -> Orientor
Note: Orientierung der Linie ändern, da diese Falsch ist
Orientor
    FLIP_APPEARANCES_CHOICE = Yes
    KIND = REVERSE
    ORIENTED -> Linien_mit_Start_Endpunkten_koord_EPSG:2056 (output)
Note: Start/Endpunkt Koordinaten umbennen
AttributeManager_2
    ATTR_TABLE:
      RENAME_SET_VALUE _z_1 > _start_z (real64)
      RENAME_SET_VALUE _x_0 > _start_x (real64)
      RENAME_SET_VALUE _y_0 > _start_y (real64)
      RENAME_SET_VALUE _z_-1 > _end_z (real64)
      RENAME_SET_VALUE _x_-1 > _end_x (real64)
      RENAME_SET_VALUE _y_-1 > _end_y (real64)
      REMOVE palette{}.value (real64)
    -> FeatureJoiner_5 [RIGHT]
Note: Startpunkt/Endpunkt Information mit Linie Joinen
FeatureJoiner_5
    ATTR_CONFLICT_RES = Prefer Left
    GEOMETRY_HANDLING = Prefer Left
    JOIN_KEYS = piste_id piste_id AUTO
    JOIN_MODE = Inner
    JOINED -> Linien_mit_Start_Endpunkten_koord_EPSG:2056 (output)

Bookmark: Höhen über DHM25 herausfinden von Pisten Start/Endpunkt
PointOnRasterValueExtractor
    INTERPOLATION_TYPE_NAME = Nearest Neighbor
    POINT -> NullAttributeMapper
NullAttributeMapper
    ATTRCHOICE = Selected Attributes
    ATTRLIST = _band{0}.palette{0}.value _band{0}.value
    NEW_VALUE = -9999
    NULL_TREATMENT = New Value
    SOURCE_ATTR_VAL = Empty "Missing (Selected Attributes Only)"
    -> ListExploder
ListExploder
    ATTR_ACCUM_MODE = Merge List Attributes
    ATTR_CONFLICT_RES = Use List Attribute Values
    INDEX_ATTR = _z_-1
    LIST_ATTR = _band{}
    ELEMENTS -> AttributeRenamer
AttributeRenamer
    ATTR_TABLE = RENAME_SET_DEFAULT value > _z_-1
    MISSING_INPUT_ATTRS = REMOVE
    -> FeatureJoiner [LEFT]
PointOnRasterValueExtractor_2
    INTERPOLATION_TYPE_NAME = Nearest Neighbor
    POINT -> NullAttributeMapper_2
NullAttributeMapper_2
    ATTRCHOICE = Selected Attributes
    ATTRLIST = _band{0}.palette{0}.value _band{0}.value
    NEW_VALUE = -9999
    NULL_TREATMENT = New Value
    SOURCE_ATTR_VAL = Empty "Missing (Selected Attributes Only)"
    -> ListExploder_2
ListExploder_2
    ATTR_ACCUM_MODE = Merge List Attributes
    ATTR_CONFLICT_RES = Use List Attribute Values
    INDEX_ATTR = _z_1
    LIST_ATTR = _band{}
    ELEMENTS -> AttributeRenamer_2
AttributeRenamer_2
    ATTR_TABLE = RENAME_SET_DEFAULT value > _z_1
    MISSING_INPUT_ATTRS = REMOVE
    -> FeatureJoiner [RIGHT]
FeatureJoiner
    ATTR_CONFLICT_RES = Prefer Left
    GEOMETRY_HANDLING = Prefer Left
    JOIN_KEYS = piste_id piste_id AUTO
    JOIN_MODE = Inner
    JOINED -> Tester_2

FME custom transformer CSV_WGS_to_LV95

Parameters:
- R_GEOMETRY =   # Geometrie Attribut
- DELIMITER = ,   # Trennzeichen CSV

CSV_WGS84 (input)
    -> AttributeSplitter
Note: Geometrie Attribute aufspiltten, werden als Liste aufgegeben
AttributeSplitter
    ATTR_NAME = r_geometry
    DELIMITER = $(DELIMITER)
    DROP_EMPTY_PARTS = No
    LIST_NAME = _list
    TRIM_OPTION = Both
    -> AttributeExposer
Note: Liste exposen um seperate x und y Koordiante erhalten
AttributeExposer
    ATTR_TABLE = _list{0},,_list{1},
    -> AttributeRenamer_9
Note: Liste zu Längen und Breitengrad umbennen
AttributeRenamer_9
    ATTR_TABLE:
      RENAME_SET_DEFAULT _list{0} > breitengrad
      RENAME_SET_DEFAULT _list{1} > längengrad
    MISSING_INPUT_ATTRS = REMOVE
    -> VertexCreator_11
Note: Punkte erstellen aus Attribtuen Lägnen/Breitengrad
VertexCreator_11
    MEASURE_TYPE = Continuous
    MODE_NAME = Replace with Point
    XVAL = @Value(längengrad)
    YVAL = @Value(breitengrad)
    -> CoordinateSystemSetter_5
Note: EPSG:4326 setzten
CoordinateSystemSetter_5
    COORDSYS = EPSG:4326
    -> Reprojector
Note: in EPSG:2056 umprojizieren
Reprojector
    DEST = EPSG:2056
    INTERPOLATION_TYPE_NAME = Nearest Neighbor
    RASTER_CELL_SIZE = Preserve Cells
    RASTER_TOLERANCE = 0.0
    SOURCE = EPSG:4326
    REPROJECTED -> LV95 (output)
LV95 (output)
